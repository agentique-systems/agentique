package ParallelFixture {
    doc /* SysML 2.0 Part 1 7.18.2: valid parallel states, outside AGQ-SEQ-01. */
    state def Health parallel {
        state operational;
        state monitoring;
    }
}
